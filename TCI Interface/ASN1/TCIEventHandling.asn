TCI-eventHandling
DEFINITIONS AUTOMATIC TAGS ::= 
BEGIN

IMPORTS
PduType FROM TCI-CommonTypes
;

EventHandling   ::= SEQUENCE {
    rxFlag              RxFlag DEFAULT '000'B,        -- receive packets with matched PSID, or receive all WSMs and ignore PSID
    eventFlag           EventFlag DEFAULT '00000000'B,-- events to be generated when packet is received, no events is generated by default
    forwardPdu          PduType OPTIONAL,             -- PDU type to forward to the Test System if rxModeFlag->includePdu is set 1
    securityFlag        SecurityFlag DEFAULT '0000'B, -- security handling for received packets
    ...,
    eventParamsChoice   EventParamsChoice OPTIONAL    -- EventParameters type included in PduEventIndication. Must be specified if RxFlag->includePduParam is set 1
}

RxFlag ::= BIT STRING {
    recvPsidMatch       (0),    -- set 0, notify about WSMs with matched PSID, ignore all others
                                -- set 1, receive all WSMs (ignore PSID filter) i.e. receive all WSMs, WSAs
    includePdu          (1),    -- if set 1 Pdu is included into PduEventIndication; if set 0, Pdu is not included
    includePduParam     (2)     -- if set 1 PduParameters is included into PduEventIndication; if set 0, PduParameters is not included
}

EventFlag ::= BIT STRING {
    e80211PktRx                     (0),    -- set 1 to be notified when inbound 802.11 frame is received by SUT
    e16093PktRx                     (1),    -- set 1 to be notified when inbound 1603 frame received SUT
    eWSM                            (2),    -- set 1 to be notified when WSM received (after PSID match filtering) by SUT
    eIpv6PktRx                      (3),    -- set 1 to be notified when inbound IPv6 frame received by SUT
    eIcmp6PktRx                     (4),    -- set 1 to be notified when Icmp echo frame is received by SUT
    ePsidServiceActive              (5),    -- set 1 to be notified when PSID service is activated (for any PSID) by SUT
    eWSAServiceActive               (6),    -- set 1 to be notified when PSID service is activated due to incoming WSA (for any /all PSID) by SUT
    eIpv6ConfigChanged              (7),    -- set 1 to be notified when IPv6 address configuration changed by SUT
    verificationCompleteWithResult  (8)     -- set 1 to be  notified when message signature verification is complete by SUT
} 

SecurityFlag ::= BIT STRING {
    bypassSecurityVerification  (0) -- if set 1, messages received without security verification, if set 0, message security verification performed per security profile
} (SIZE(4))


EventParamsChoice ::= ENUMERATED {
      service           (0),
      wsm               (1),
      ip                (2),
      d80211frame       (3),
      security          (4)
}

END
