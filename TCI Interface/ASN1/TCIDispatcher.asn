--<OSS.PDU TCI-MsgDispatcher.TCIMessage>--
TCI-Dispatcher
DEFINITIONS AUTOMATIC TAGS ::= 
BEGIN

IMPORTS

TCI16093            FROM TCI-16093
TCI16094            FROM TCI-16094
TCI80211            FROM TCI-80211
TCI29451            FROM TCI-29451
TCISutControl       FROM TCI-SutControl
Time64              FROM TCI-CommonTypes

;

TCIMsg ::= SEQUENCE{
    version     INTEGER {currentVersion(2)} (1..127),  -- current protocol version 2
    time        Time64,                                -- UTC timestamp with milliseconds, GPS syncronized
    frame       Frame,                                 -- protocol layer
    ...
    }

Frame ::=CHOICE {
    d16093 [1] TCI16093,
    --d16092 [2] TCI16092, module is redundant with TCI16093
    d80211 [3] TCI80211,
    d16094 [4] TCI16094,
    d29451 [5] TCI29451,
    sutCtrl [6] TCISutControl,
    ...
}

END
